module sonic-vxlan {
    namespace "http://github.com/Azure/sonic-vxlan";
    prefix svxlan;
    yang-version 1.1;

    import ietf-yang-types {
        prefix yang;
    }

    import ietf-inet-types {
        prefix inet;
    }

    import sonic-extension {
        prefix sonic-ext;
    }
    import sonic-vlan {
        prefix svlan;
    }


    organization
        "SONiC";

    contact
        "SONiC";

    description
        "SONIC VXLAN";

    revision 2021-04-12 {
        description
            "First revision.";
    }

    container sonic-vxlan {

        container VXLAN_TUNNEL {

            list VXLAN_TUNNEL_LIST {
                key "name";
                max-elements 1;

                leaf name {
                    must "(starts-with(../name, 'vtep'))"
                    {
                        error-message "Error: Name should start with vtep";
                        error-app-tag invalid-vtep-name;
                    }
                    type string {
                        length 1..10;
                    }
                }

                leaf src_ip {
                    type inet:ipv4-address;
                }
            }
        }

        container VXLAN_TUNNEL_MAP {

            list VXLAN_TUNNEL_MAP_LIST {
                key "name mapname";

                leaf name {
                    type leafref {
                        path "../../../VXLAN_TUNNEL/VXLAN_TUNNEL_LIST/name";
                    }
                }

                leaf mapname {
                    type string;
                }

                leaf vlan {
                    mandatory true;
                    type leafref {
                        path "/svlan:sonic-vlan/svlan:VLAN/svlan:VLAN_LIST/svlan:name";
                    }

                }

                leaf vni {
                    mandatory true;
                    type uint32 {
                        range "1..16777215" {
                            error-message "Error: VNI ID out of range";
                            error-app-tag vnid-invalid;
                        }
                    }
                }
            }
        }

        container VXLAN_EVPN_NVO {

            list VXLAN_EVPN_NVO_LIST { 

                key "name";
                max-elements 1;

                leaf name {
                    type string;
                }

                leaf source_vtep {
                    mandatory true;
                    type leafref {
                        path "../../../VXLAN_TUNNEL/VXLAN_TUNNEL_LIST/name";
                    }
                }
            }
        }
        container VXLAN_TUNNEL_TABLE { 
            sonic-ext:db-name "STATE_DB"; 
            sonic-ext:key-delim ":"; 

            config false;
            description "state db vxlan tunnel table";

            list VXLAN_TUNNEL_TABLE_LIST { 
                key "name";

                leaf name {
                    type string; 
                }

                leaf src_ip {
                    type string;
                }

                leaf dst_ip {
                    type string;
                }

                leaf tnl_src {
                    type string;
                }

                leaf operstatus {
                    type string;
                }
            }
        }
        container VXLAN_REMOTE_VNI_TABLE {
            sonic-ext:db-name "APPL_DB";
            sonic-ext:key-delim ":";

            config false;
            description "app db vxlan remote vni table";

            list VXLAN_REMOTE_VNI_TABLE_LIST {
                key "vlan remote_vtep";

                leaf vlan {
                    type leafref {
                        path "/svlan:sonic-vlan/svlan:VLAN/svlan:VLAN_LIST/svlan:name";
                    }
                }

                leaf remote_vtep {
                    type inet:ipv4-address;
                }

                leaf vni {
                    type string;
                }
            }
        }
        container VXLAN_FDB_TABLE{
            sonic-ext:db-name "APPL_DB";
            sonic-ext:key-delim ":";

            config false;
            description "app db vxlan fdb table";

            list VXLAN_FDB_TABLE_LIST {
                key "vlan mac_addr";

                leaf vlan {
                    type leafref {
                        path "/svlan:sonic-vlan/svlan:VLAN/svlan:VLAN_LIST/svlan:name";
                    }
                }

                leaf mac_addr {
                    type yang:mac-address;
                }

                leaf remote_vtep {
                    type inet:ipv4-address;
                }

                leaf type {
                    type string;
                }

                leaf vni {
                    type string;
                }
            }
        }
    }
}
